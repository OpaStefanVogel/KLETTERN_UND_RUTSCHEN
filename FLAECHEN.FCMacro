App.closeDocument("Unnamed")

Gui.runCommand('Std_Workbench',18)
Gui.activateWorkbench("StartWorkbench")
Gui.runCommand('Std_ViewStatusBar',1)

### Begin command Std_New
App.newDocument("Unnamed")
# App.setActiveDocument("Unnamed")
# App.ActiveDocument=App.getDocument("Unnamed")
# Gui.ActiveDocument=Gui.getDocument("Unnamed")
Gui.activeDocument().activeView().viewDefaultOrientation()
### End command Std_New

Gui.runCommand('Std_OrthographicCamera',1)

### Begin command Std_Workbench
Gui.activateWorkbench("PartWorkbench")
Gui.runCommand('Std_Workbench',10)
### End command Std_Workbench

### Begin command Part_Box
App.ActiveDocument.addObject("Part::Box","Box")
App.ActiveDocument.ActiveObject.Label = "Cube"
App.ActiveDocument.recompute()
Gui.SendMsgToActiveView("ViewFit")
### End command Part_Box
# Gui.Selection.addSelection('Unnamed','Box')
Gui.runCommand('Std_ViewDockUndockFullscreen',1)
FreeCAD.getDocument('Unnamed').getObject('Box').Length = '300 mm'
FreeCAD.getDocument('Unnamed').getObject('Box').Width = '100 mm'
FreeCAD.getDocument('Unnamed').getObject('Box').Height = '200 mm'

### Begin command Part_Box
App.ActiveDocument.addObject("Part::Box","Box")
App.ActiveDocument.ActiveObject.Label = "Cube"
App.ActiveDocument.recompute()
Gui.SendMsgToActiveView("ViewFit")
### End command Part_Box
# Gui.Selection.addSelection('Unnamed','Box001')
FreeCAD.getDocument('Unnamed').getObject('Box001').Length = '105 mm'
FreeCAD.getDocument('Unnamed').getObject('Box001').Width = '50 mm'
FreeCAD.getDocument('Unnamed').getObject('Box001').Height = '60 mm'
FreeCAD.getDocument('Unnamed').getObject('Box001').Placement.translate(FreeCAD.Vector(55,65,50))

### Begin command Part_Box
App.ActiveDocument.addObject("Part::Box","Box")
App.ActiveDocument.ActiveObject.Label = "Cube"
App.ActiveDocument.recompute()
Gui.SendMsgToActiveView("ViewFit")
### End command Part_Box
# Gui.Selection.clearSelection()
# Gui.Selection.addSelection('Unnamed','Box002')
FreeCAD.getDocument('Unnamed').getObject('Box002').Placement.translate(FreeCAD.Vector(60,70,100))
FreeCAD.getDocument('Unnamed').getObject('Box002').Length = '100 mm'
FreeCAD.getDocument('Unnamed').getObject('Box002').Width = '50 mm'
FreeCAD.getDocument('Unnamed').getObject('Box002').Height = '60 mm'

# Gui.Selection.clearSelection()
# Gui.Selection.addSelection('Unnamed','Box')
# Gui.Selection.addSelection('Unnamed','Box001')
### Begin command Part_Cut
App.activeDocument().addObject("Part::Cut","Cut")
App.activeDocument().Cut.Base = App.activeDocument().Box
App.activeDocument().Cut.Tool = App.activeDocument().Box001
Gui.activeDocument().Box.Visibility=False
Gui.activeDocument().Box001.Visibility=False
App.getDocument('Unnamed').getObject('Cut').ViewObject.ShapeColor=getattr(App.getDocument('Unnamed').getObject('Box').getLinkedObject(True).ViewObject,'ShapeColor',App.getDocument('Unnamed').getObject('Cut').ViewObject.ShapeColor)
App.getDocument('Unnamed').getObject('Cut').ViewObject.DisplayMode=getattr(App.getDocument('Unnamed').getObject('Box').getLinkedObject(True).ViewObject,'DisplayMode',App.getDocument('Unnamed').getObject('Cut').ViewObject.DisplayMode)
App.ActiveDocument.recompute()
### End command Part_Cut

# Gui.Selection.clearSelection()
# Gui.Selection.addSelection('Unnamed','Cut')
# Gui.Selection.addSelection('Unnamed','Box002')
### Begin command Part_Cut
App.activeDocument().addObject("Part::Cut","Cut001")
App.activeDocument().Cut001.Base = App.activeDocument().Cut
App.activeDocument().Cut001.Tool = App.activeDocument().Box002
Gui.activeDocument().Cut.Visibility=False
Gui.activeDocument().Box002.Visibility=False
App.getDocument('Unnamed').getObject('Cut001').ViewObject.ShapeColor=getattr(App.getDocument('Unnamed').getObject('Cut').getLinkedObject(True).ViewObject,'ShapeColor',App.getDocument('Unnamed').getObject('Cut001').ViewObject.ShapeColor)
App.getDocument('Unnamed').getObject('Cut001').ViewObject.DisplayMode=getattr(App.getDocument('Unnamed').getObject('Cut').getLinkedObject(True).ViewObject,'DisplayMode',App.getDocument('Unnamed').getObject('Cut001').ViewObject.DisplayMode)
App.ActiveDocument.recompute()
### End command Part_Cut

# Gui.Selection.clearSelection()
# Gui.Selection.addSelection('Unnamed','Cut001')
### Begin command Std_SendToPythonConsole
obj = App.getDocument("Unnamed").getObject("Cut001")
### End command Std_SendToPythonConsole
for e in obj.Shape.Vertexes:
   print(e.Point)

### Begin command Part_Box
App.ActiveDocument.addObject("Part::Box","Box")
App.ActiveDocument.ActiveObject.Label = "Cube"
App.ActiveDocument.recompute()
Gui.SendMsgToActiveView("ViewFit")
### End command Part_Box
# Gui.Selection.clearSelection()
# Gui.Selection.addSelection('Unnamed','Box003')
FreeCAD.getDocument('Unnamed').getObject('Box003').Length = '355 mm'
FreeCAD.getDocument('Unnamed').getObject('Box003').Width = '115 mm'
FreeCAD.getDocument('Unnamed').getObject('Box003').Height = '115 mm'
FreeCAD.getDocument('Unnamed').getObject('Box003').Placement.translate(FreeCAD.Vector(120,0,185))
FreeCAD.getDocument('Unnamed').getObject('Box003').Placement.rotate(FreeCAD.Vector(0,0,0),FreeCAD.Vector(0,1,0),-80.79959953092967)
FreeCAD.getDocument('Unnamed').getObject('Box003').Placement.rotate(FreeCAD.Vector(0,0,0),FreeCAD.Vector(0,1,0),72.05059700708613)
FreeCAD.getDocument('Unnamed').getObject('Box003').Placement.rotate(FreeCAD.Vector(0,0,0),FreeCAD.Vector(115/2,0,-355),-8.759726433781287)
obj = App.getDocument("Unnamed").getObject("Box003")
for e in obj.Shape.Vertexes:
   print(e.Point)
